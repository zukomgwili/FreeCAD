# SPDX-License-Identifier: LGPL-2.1-or-later
"""Stock TechDraw qualification in a disposable GUI process.

The launcher must provide isolated user/system configurations, TD_NATIVE_OUTPUT,
TD_NATIVE_BYPASS_MODULE, TD_NATIVE_QT_LIB and authenticated TD_NATIVE_MACRO_PATH/
TD_NATIVE_MACRO_SHA256. The module is a scratch build with
both FreeCAD mitigations bypassed. Only public model/view properties and stock
GUI export commands create the drawing. No graphics item or pen is injected.
This macro exits the disposable process after saving its evidence.
"""

import ctypes
from ctypes import wintypes
import hashlib
import json
import math
import os
from pathlib import Path
import sys
import time
import traceback
import unittest

import FreeCAD as App
import FreeCADGui as Gui
from PySide import QtCore, QtGui, QtWidgets
from PySide6 import QtPrintSupport


def digest(path):
    return hashlib.sha256(Path(path).read_bytes()).hexdigest()


def settle(milliseconds=300):
    loop = QtCore.QEventLoop()
    QtCore.QTimer.singleShot(milliseconds, loop.quit)
    loop.exec()


def color_rgba(color):
    return [color.red(), color.green(), color.blue(), color.alpha()]


def ready_box_face(scene):
    """Recognize the complete projected face of this fixture's unchanged box."""
    if len(scene["faces"]) != 1:
        return False
    face = scene["faces"][0]
    elements = face["elements"]
    return bool(
        face["type"] == 65556
        and face["visible"]
        and not face["empty"]
        and face["bounds"] == [-50.0, -50.0, 100.0, 100.0]
        and math.isclose(face["length_scene"], 400.0, abs_tol=1e-6)
        and 5 <= len(elements) <= 12
        and elements[0][:2] == elements[-1][:2]
        and all(element[2] in (0, 1) for element in elements)
        and all(
            math.isfinite(value) and value in (-50.0, 50.0)
            for element in elements
            for value in element[:2]
        )
    )


def wait_for_box_face(read_scene, request_paint, active_threads, pause, observe, clock):
    """Drain HLR/face callbacks and observe two identical complete face samples.

    DrawViewPart starts HLR and then face extraction with QtConcurrent::run on
    Qt's global pool. Its public requestPaint redraws from getFaceGeometry,
    which returns no faces until extraction finishes. An idle pool alone does
    not consume the queued finished callback that starts the next task.
    """
    deadline = clock() + 20.0
    previous = None
    stable = 0
    while clock() < deadline:
        pause(50)
        active = active_threads()
        if active == 0:
            request_paint()
            pause(50)
            active = active_threads()
        scene = read_scene()
        complete = active == 0 and ready_box_face(scene)
        sample = {"faces": scene["faces"], "paths": scene["paths"]}
        stable = stable + 1 if complete and sample == previous else int(complete)
        previous = sample if complete else None
        observe(
            {"active_threads": active, "face_count": len(scene["faces"]), "stable_samples": stable}
        )
        if stable == 2 and clock() < deadline:
            return scene, {
                "policy": "global-thread-pool-idle/painted-box-face-v1",
                "active_threads": 0,
                "face_count": 1,
                "stable_samples": 2,
                "poll_ms": 50,
                "timeout_ms": 20000,
            }
    raise AssertionError("Timed out waiting for complete stable TechDraw box face geometry")


def text_palette_record():
    # Read Qt's constructor default with an unattached item; never add it to the scene.
    text = QtWidgets.QGraphicsTextItem()
    return {
        "application_rgba": color_rgba(QtWidgets.QApplication.palette().color(QtGui.QPalette.Text)),
        "widget_text_control_rgba": color_rgba(
            QtWidgets.QApplication.palette("QWidgetTextControl").color(QtGui.QPalette.Text)
        ),
        "new_graphics_text_rgba": color_rgba(text.defaultTextColor()),
    }


def null_origin_frame_expectation(scene, palette, required_count):
    # QGIViewDimension always frames its unused origin label. QGIDatumLabel
    # initializes that pen from the text-control palette, and setNormalColorAll
    # leaves it unchanged. Only a translucent pen takes Qt PDF's stroker route.
    assert type(required_count) is int and required_count >= 0, required_count
    assert set(palette) == {
        "application_rgba",
        "widget_text_control_rgba",
        "new_graphics_text_rgba",
    }, palette
    for rgba in palette.values():
        assert len(rgba) == 4 and all(
            type(value) is int and 0 <= value <= 255 for value in rgba
        ), palette
    assert palette["new_graphics_text_rgba"] == palette["widget_text_control_rgba"], palette
    for frame in scene["rectangles"]:
        assert all(
            type(frame[key]) is bool for key in ("visible", "null", "qt_pen_is_cosmetic")
        ), frame
        assert all(
            type(frame[key]) is int
            for key in ("type", "alpha", "pen_style", "pen_brush_style", "brush_style")
        ), frame
        assert len(frame["rgba"]) == 4 and all(
            type(value) is int and 0 <= value <= 255 for value in frame["rgba"]
        ), frame
        for key, count in (("rect", 4), ("scene_transform", 9)):
            assert len(frame[key]) == count and all(
                type(value) in (int, float) and math.isfinite(value) for value in frame[key]
            ), frame
        assert all(
            type(frame[key]) in (int, float) and math.isfinite(frame[key])
            for key in ("width_scene", "effective_opacity")
        ), frame
    frames = [frame for frame in scene["rectangles"] if frame["visible"] and frame["null"]]
    assert len(frames) == required_count, (required_count, frames)
    for frame in frames:
        assert frame["type"] == 65540 and frame["rect"] == [0.0, 0.0, 0.0, 0.0], frame
        assert frame["rgba"] == palette["new_graphics_text_rgba"], (frame, palette)
        assert frame["alpha"] == frame["rgba"][3] and 0 < frame["alpha"] <= 255, frame
        assert frame["width_scene"] == 5.0 and not frame["qt_pen_is_cosmetic"], frame
        assert frame["pen_style"] == QtCore.Qt.SolidLine.value, frame
        assert frame["pen_brush_style"] == QtCore.Qt.SolidPattern.value, frame
        assert frame["brush_style"] == QtCore.Qt.NoBrush.value, frame
        assert frame["effective_opacity"] == 1.0, frame
        transform = frame["scene_transform"]
        assert len(transform) == 9 and all(math.isfinite(value) for value in transform), frame
        # An affine transform preserves a null rectangle; no identity assumption is needed.
        assert [transform[2], transform[5], transform[8]] == [0.0, 0.0, 1.0], frame
    frames.sort(key=lambda frame: json.dumps(frame, sort_keys=True))
    translucent = sum(0 < frame["alpha"] < 255 for frame in frames)
    return {
        "required_count": required_count,
        "actual_count": len(frames),
        "translucent_count": translucent,
        "baseline_invalid_closes": translucent,
        "frames": frames,
    }


def loaded_images():
    if sys.platform == "darwin":
        dyld = ctypes.CDLL(None)
        count = dyld._dyld_image_count
        count.restype = ctypes.c_uint32
        name = dyld._dyld_get_image_name
        name.argtypes = [ctypes.c_uint32]
        name.restype = ctypes.c_char_p
        return sorted({os.fsdecode(name(index)) for index in range(count())})
    if sys.platform.startswith("linux"):
        names = []
        for line in Path("/proc/self/maps").read_text().splitlines():
            fields = line.split(maxsplit=5)
            if len(fields) == 6 and fields[5].startswith("/"):
                names.append(fields[5])
        return sorted(set(names))
    if sys.platform == "win32":

        class ModuleEntry(ctypes.Structure):
            _fields_ = [
                ("dwSize", wintypes.DWORD),
                ("th32ModuleID", wintypes.DWORD),
                ("th32ProcessID", wintypes.DWORD),
                ("GlblcntUsage", wintypes.DWORD),
                ("ProccntUsage", wintypes.DWORD),
                ("modBaseAddr", ctypes.c_void_p),
                ("modBaseSize", wintypes.DWORD),
                ("hModule", wintypes.HMODULE),
                ("szModule", wintypes.WCHAR * 256),
                ("szExePath", wintypes.WCHAR * 260),
            ]

        kernel = ctypes.WinDLL("kernel32", use_last_error=True)
        snapshot = kernel.CreateToolhelp32Snapshot
        snapshot.argtypes = [wintypes.DWORD, wintypes.DWORD]
        snapshot.restype = wintypes.HANDLE
        first = kernel.Module32FirstW
        next_module = kernel.Module32NextW
        for function in (first, next_module):
            function.argtypes = [wintypes.HANDLE, ctypes.POINTER(ModuleEntry)]
            function.restype = wintypes.BOOL
        close = kernel.CloseHandle
        close.argtypes = [wintypes.HANDLE]
        close.restype = wintypes.BOOL
        handle = snapshot(0x8 | 0x10, os.getpid())
        if handle == ctypes.c_void_p(-1).value:
            raise ctypes.WinError(ctypes.get_last_error())
        names = []
        try:
            entry = ModuleEntry()
            entry.dwSize = ctypes.sizeof(entry)
            if not first(handle, ctypes.byref(entry)):
                raise ctypes.WinError(ctypes.get_last_error())
            while True:
                names.append(entry.szExePath)
                if not next_module(handle, ctypes.byref(entry)):
                    if ctypes.get_last_error() != 18:  # ERROR_NO_MORE_FILES
                        raise ctypes.WinError(ctypes.get_last_error())
                    break
        finally:
            close(handle)
        return sorted(set(names))
    raise RuntimeError("Native loaded-library proof is unsupported on this platform")


def cocoa_print_panel_state():
    """Read the active modal window belonging to this process's AppKit application."""
    objc = ctypes.CDLL("/usr/lib/libobjc.A.dylib")
    objc.objc_getClass.argtypes = [ctypes.c_char_p]
    objc.objc_getClass.restype = ctypes.c_void_p
    objc.sel_registerName.argtypes = [ctypes.c_char_p]
    objc.sel_registerName.restype = ctypes.c_void_p
    objc.object_getClassName.argtypes = [ctypes.c_void_p]
    objc.object_getClassName.restype = ctypes.c_char_p
    send_object = ctypes.CFUNCTYPE(ctypes.c_void_p, ctypes.c_void_p, ctypes.c_void_p)(
        ("objc_msgSend", objc)
    )
    send_bool = ctypes.CFUNCTYPE(ctypes.c_bool, ctypes.c_void_p, ctypes.c_void_p)(
        ("objc_msgSend", objc)
    )
    send_kind = ctypes.CFUNCTYPE(ctypes.c_bool, ctypes.c_void_p, ctypes.c_void_p, ctypes.c_void_p)(
        ("objc_msgSend", objc)
    )
    send_count = ctypes.CFUNCTYPE(ctypes.c_ulong, ctypes.c_void_p, ctypes.c_void_p)(
        ("objc_msgSend", objc)
    )
    send_index = ctypes.CFUNCTYPE(
        ctypes.c_void_p, ctypes.c_void_p, ctypes.c_void_p, ctypes.c_ulong
    )(("objc_msgSend", objc))
    send_utf8 = ctypes.CFUNCTYPE(ctypes.c_char_p, ctypes.c_void_p, ctypes.c_void_p)(
        ("objc_msgSend", objc)
    )
    application = send_object(
        objc.objc_getClass(b"NSApplication"),
        objc.sel_registerName(b"sharedApplication"),
    )
    window = send_object(application, objc.sel_registerName(b"modalWindow"))
    windows = send_object(application, objc.sel_registerName(b"windows"))
    count = send_count(windows, objc.sel_registerName(b"count"))
    assert count < 1000, "Unexpected AppKit window inventory"
    owned = [
        send_index(windows, objc.sel_registerName(b"objectAtIndex:"), index)
        for index in range(count)
    ]
    title = send_object(window, objc.sel_registerName(b"title")) if window else None
    return {
        "window": window or 0,
        "class": objc.object_getClassName(window).decode() if window else None,
        "visible": send_bool(window, objc.sel_registerName(b"isVisible")) if window else False,
        "owned": window in owned if window else False,
        "panel": (
            send_kind(
                window, objc.sel_registerName(b"isKindOfClass:"), objc.objc_getClass(b"NSPanel")
            )
            if window
            else False
        ),
        "title": send_utf8(title, objc.sel_registerName(b"UTF8String")).decode() if title else None,
    }


def ready_cocoa_print_panel(state):
    # Native qualification uses the English Print panel, as on the Windows route.
    return bool(
        state["window"]
        and state["visible"]
        and state["owned"]
        and state["panel"]
        and state["title"] == "Print"
    )


def accept_cocoa_print_panel(result, expected_window):
    """Complete only the observed active owned Print panel through public AppKit API."""
    state = cocoa_print_panel_state()
    assert ready_cocoa_print_panel(state) and state["window"] == expected_window, state
    objc = ctypes.CDLL("/usr/lib/libobjc.A.dylib")
    objc.objc_getClass.argtypes = [ctypes.c_char_p]
    objc.objc_getClass.restype = ctypes.c_void_p
    objc.sel_registerName.argtypes = [ctypes.c_char_p]
    objc.sel_registerName.restype = ctypes.c_void_p
    send_object = ctypes.CFUNCTYPE(ctypes.c_void_p, ctypes.c_void_p, ctypes.c_void_p)(
        ("objc_msgSend", objc)
    )
    send_integer = ctypes.CFUNCTYPE(None, ctypes.c_void_p, ctypes.c_void_p, ctypes.c_long)(
        ("objc_msgSend", objc)
    )
    application = send_object(
        objc.objc_getClass(b"NSApplication"),
        objc.sel_registerName(b"sharedApplication"),
    )
    send_integer(application, objc.sel_registerName(b"stopModalWithCode:"), result)


def windows_print_panel_state():
    """Observe current-thread windows, including an incompletely created panel."""
    user = ctypes.WinDLL("user32", use_last_error=True)
    kernel = ctypes.WinDLL("kernel32", use_last_error=True)
    kernel.GetCurrentThreadId.restype = wintypes.DWORD
    thread = kernel.GetCurrentThreadId()
    callback_type = ctypes.WINFUNCTYPE(wintypes.BOOL, wintypes.HWND, wintypes.LPARAM)
    user.EnumThreadWindows.argtypes = [wintypes.DWORD, callback_type, wintypes.LPARAM]
    user.EnumThreadWindows.restype = wintypes.BOOL
    user.GetWindowThreadProcessId.argtypes = [
        wintypes.HWND,
        ctypes.POINTER(wintypes.DWORD),
    ]
    user.GetWindowThreadProcessId.restype = wintypes.DWORD
    for name in ("IsWindowVisible", "IsWindowEnabled"):
        function = getattr(user, name)
        function.argtypes = [wintypes.HWND]
        function.restype = wintypes.BOOL
    for name in ("GetClassNameW", "GetWindowTextW"):
        function = getattr(user, name)
        function.argtypes = [wintypes.HWND, wintypes.LPWSTR, ctypes.c_int]
        function.restype = ctypes.c_int
    user.GetDlgItem.argtypes = [wintypes.HWND, ctypes.c_int]
    user.GetDlgItem.restype = wintypes.HWND

    def text(hwnd, function):
        buffer = ctypes.create_unicode_buffer(256)
        getattr(user, function)(hwnd, buffer, len(buffer))
        return buffer.value

    windows = []

    @callback_type
    def observe(hwnd, unused):
        process = wintypes.DWORD()
        observed_thread = user.GetWindowThreadProcessId(hwnd, ctypes.byref(process))
        button = user.GetDlgItem(hwnd, 1)  # IDOK in the standard Print property sheet.
        button_process = wintypes.DWORD()
        button_thread = (
            user.GetWindowThreadProcessId(button, ctypes.byref(button_process)) if button else 0
        )
        windows.append(
            {
                "dialog_handle": hwnd,
                "process_id": process.value,
                "thread_id": observed_thread,
                "visible": bool(user.IsWindowVisible(hwnd)),
                "dialog_class": text(hwnd, "GetClassNameW"),
                "title": text(hwnd, "GetWindowTextW"),
                "button_handle": button or 0,
                "button_id": 1,
                "button_process_id": button_process.value,
                "button_thread_id": button_thread,
                "button_visible": bool(button and user.IsWindowVisible(button)),
                "button_enabled": bool(button and user.IsWindowEnabled(button)),
                "button_class": text(button, "GetClassNameW") if button else None,
                "button_label": text(button, "GetWindowTextW") if button else None,
            }
        )
        return len(windows) < 1000

    if not user.EnumThreadWindows(thread, observe, 0):
        raise ctypes.WinError(ctypes.get_last_error())
    assert len(windows) < 1000, "Unexpected Windows thread window inventory"
    return {"process_id": os.getpid(), "thread_id": thread, "windows": windows}


def windows_print_panel_candidates(state):
    return [
        window
        for window in state["windows"]
        if window["process_id"] == state["process_id"]
        and window["thread_id"] == state["thread_id"]
        and window["dialog_handle"]
        and window["visible"]
        and window["dialog_class"] == "#32770"
        and window["title"] == "Print"
        and window["button_handle"]
        and window["button_id"] == 1
        and window["button_process_id"] == state["process_id"]
        and window["button_thread_id"] == state["thread_id"]
        and window["button_visible"]
        and window["button_enabled"]
        and window["button_class"] == "Button"
        and window["button_label"].replace("&", "").casefold() == "print"
    ]


def ready_windows_print_panel(state):
    candidates = windows_print_panel_candidates(state)
    assert len(candidates) <= 1, "Ambiguous owned native Print property sheets"
    return len(candidates) == 1


def accept_windows_print_panel(expected):
    """Recheck and click only the observed owned native English Print button."""
    state = windows_print_panel_state()
    assert ready_windows_print_panel(state), state
    current = windows_print_panel_candidates(state)[0]
    assert current == expected, (expected, current)
    user = ctypes.WinDLL("user32", use_last_error=True)
    user.SetActiveWindow.argtypes = [wintypes.HWND]
    user.SetActiveWindow.restype = wintypes.HWND
    user.SendMessageW.argtypes = [
        wintypes.HWND,
        wintypes.UINT,
        wintypes.WPARAM,
        wintypes.LPARAM,
    ]
    user.SendMessageW.restype = ctypes.c_ssize_t
    user.SetActiveWindow(current["dialog_handle"])
    user.SendMessageW(current["button_handle"], 0x00F5, 0, 0)  # Documented BM_CLICK.
    return current


output = Path(os.environ["TD_NATIVE_OUTPUT"]).resolve()
module_path = Path(os.environ["TD_NATIVE_BYPASS_MODULE"]).resolve()
qt_lib = Path(os.environ["TD_NATIVE_QT_LIB"]).resolve()
qt_prefix = Path(os.environ.get("TD_NATIVE_QT_PREFIX", str(qt_lib.parent))).resolve()
plugin_root = Path(
    os.environ.get("TD_NATIVE_PLUGIN_ROOT", str(qt_lib.parent / "plugins"))
).resolve()
assert os.environ.get("TD_NATIVE_DISPOSABLE") == "1", "Use the isolated native launcher"
expected_qt_version = os.environ.get("TD_NATIVE_EXPECTED_QT_VERSION", "6.11.2")
assert expected_qt_version in ("6.11.1", "6.11.2"), "Unsupported expected Qt version"
assert QtCore.qVersion() == expected_qt_version, "Actual Qt version differs from the selected mode"
macro_path = Path(os.environ["TD_NATIVE_MACRO_PATH"]).resolve()
macro_source = {"path": str(macro_path), "sha256": digest(macro_path)}
assert macro_source["sha256"] == os.environ["TD_NATIVE_MACRO_SHA256"], "Macro source changed"
output.mkdir(parents=True, exist_ok=True)
assert not (output / "manifest.json").exists(), "Preserve existing evidence"
log = open(output / "macro.log", "w", buffering=1)
sys.stdout = sys.stderr = log
preferences = {
    "Colors": App.ParamGet("User parameter:BaseApp/Preferences/Mod/TechDraw/Colors"),
    "View": App.ParamGet("User parameter:BaseApp/Preferences/Mod/TechDraw/View"),
    "Standards": App.ParamGet("User parameter:BaseApp/Preferences/Mod/TechDraw/Standards"),
    "General": App.ParamGet("User parameter:BaseApp/Preferences/Mod/TechDraw/General"),
    "Dialog": App.ParamGet("User parameter:BaseApp/Preferences/Dialog"),
    "Files": App.ParamGet("User parameter:BaseApp/Preferences/Mod/TechDraw/Files"),
    "Mod": App.ParamGet("User parameter:BaseApp/Preferences/Mod"),
}
line_group = App.getResourceDir() + "Mod/TechDraw/LineGroup/"
settings = [
    ("Colors", "Unsigned", "NormalColor", 0x000000FF, 0x000000FF),
    ("Colors", "Bool", "LightOnDark", False, False),
    ("View", "Bool", "ScreenMode", True, True),
    ("Standards", "Int", "LineStandard", 1, 1),
    ("General", "Int", "EdgeCapStyle", 0x20, 2),
    ("Dialog", "Bool", "DontUseNativeDialog", False, True),
    ("Files", "String", "LineDefLocation", line_group, line_group),
    ("Files", "String", "LineElementLocation", line_group, line_group),
    ("Mod", "Int", "PDFVersion", 0, 0),
]
previous = [
    getattr(preferences[group], "Get" + kind)(key, default)
    for group, kind, key, default, value in settings
]
cases = []
records = []
exit_code = 1

try:
    assert not Gui.Control.activeDialog()
    assert "TechDrawGui" not in sys.modules, "Scratch module must load before the workbench"
    for group, kind, key, default, value in settings:
        getattr(preferences[group], "Set" + kind)(key, value)
    QtWidgets.QApplication.setAttribute(QtCore.Qt.AA_DontUseNativeDialogs, True)
    sys.path.insert(0, str(module_path.parent))
    import Part
    import TechDraw
    import TechDrawGui

    assert Path(TechDrawGui.__file__).resolve() == module_path, TechDrawGui.__file__
    bypass = json.loads((module_path.parent / "bypass-provenance.json").read_text())
    assert digest(module_path) == bypass["module_sha256"]
    Gui.activateWorkbench("TechDrawWorkbench")
    if os.environ.get("TD_NATIVE_RUN_GUI_TESTS", "1") == "1":
        suite = unittest.defaultTestLoader.loadTestsFromName("TestTechDrawGui")
        result = unittest.TextTestRunner(stream=log, verbosity=2).run(suite)
        assert result.wasSuccessful() and result.testsRun >= 11
        records.append({"gui_tests": result.testsRun, "failures": 0, "errors": 0})

    document = App.newDocument("NativeQtPdfQualification", hidden=True)
    box = document.addObject("Part::Box", "Box")
    page = document.addObject("TechDraw::DrawPage", "Page")
    template = document.addObject("TechDraw::DrawSVGTemplate", "Template")
    template.Template = (
        App.getResourceDir() + "Mod/TechDraw/Templates/Default_Template_A4_Landscape.svg"
    )
    page.Template = template
    view = document.addObject("TechDraw::DrawViewPart", "View")
    view.Source = [box]
    view.Direction = App.Vector(0, 0, 1)
    view.X = 100
    view.Y = 100
    page.addView(view)
    document.recompute()
    page.ViewObject.show()
    settle(2000)
    assert len(view.getVisibleEdges()) == 4

    def scene_record():
        paths = []
        faces = []
        rectangles = []
        seen = set()
        for top in QtWidgets.QApplication.instance().topLevelWidgets():
            for viewport in top.findChildren(QtWidgets.QGraphicsView):
                scene = viewport.scene()
                if scene is None or id(scene) in seen:
                    continue
                seen.add(id(scene))
                # Do not wrap custom parents; only read native item values.
                for item in scene.items():
                    if isinstance(item, QtWidgets.QGraphicsPathItem) and item.type() == 65555:
                        path = item.path()
                        pen = item.pen()
                        paths.append(
                            {
                                "elements": [
                                    [
                                        path.elementAt(i).x,
                                        path.elementAt(i).y,
                                        path.elementAt(i).type.value,
                                    ]
                                    for i in range(path.elementCount())
                                ],
                                "empty": path.isEmpty(),
                                "visible": item.isVisible(),
                                "length_scene": path.length(),
                                "width_scene": pen.widthF(),
                                "alpha": pen.color().alpha(),
                                "qt_pen_is_cosmetic": pen.isCosmetic(),
                                "style": pen.style().value,
                                "cap": pen.capStyle().value,
                                "dash_pattern": list(pen.dashPattern()),
                                "dash_offset": pen.dashOffset(),
                            }
                        )
                    if isinstance(item, QtWidgets.QGraphicsPathItem) and item.type() == 65556:
                        path = item.path()
                        pen = item.pen()
                        brush = item.brush()
                        bounds = path.boundingRect()
                        transform = item.sceneTransform()
                        faces.append(
                            {
                                "type": item.type(),
                                "elements": [
                                    [
                                        path.elementAt(i).x,
                                        path.elementAt(i).y,
                                        path.elementAt(i).type.value,
                                    ]
                                    for i in range(path.elementCount())
                                ],
                                "empty": path.isEmpty(),
                                "visible": item.isVisible(),
                                "bounds": [
                                    bounds.x(),
                                    bounds.y(),
                                    bounds.width(),
                                    bounds.height(),
                                ],
                                "length_scene": path.length(),
                                "fill_rule": path.fillRule().value,
                                "brush_style": brush.style().value,
                                "brush_rgba": color_rgba(brush.color()),
                                "pen_style": pen.style().value,
                                "pen_rgba": color_rgba(pen.color()),
                                "width_scene": pen.widthF(),
                                "qt_pen_is_cosmetic": pen.isCosmetic(),
                                "cap": pen.capStyle().value,
                                "join": pen.joinStyle().value,
                                "dash_pattern": list(pen.dashPattern()),
                                "dash_offset": pen.dashOffset(),
                                "effective_opacity": item.effectiveOpacity(),
                                "scene_transform": [
                                    transform.m11(),
                                    transform.m12(),
                                    transform.m13(),
                                    transform.m21(),
                                    transform.m22(),
                                    transform.m23(),
                                    transform.m31(),
                                    transform.m32(),
                                    transform.m33(),
                                ],
                            }
                        )
                    if isinstance(item, QtWidgets.QGraphicsRectItem) and item.type() in (3, 65540):
                        rect = item.rect()
                        pen = item.pen()
                        transform = item.sceneTransform()
                        rectangles.append(
                            {
                                "type": item.type(),
                                "rect": [
                                    rect.x(),
                                    rect.y(),
                                    rect.width(),
                                    rect.height(),
                                ],
                                "visible": item.isVisible(),
                                "null": rect.isNull(),
                                "alpha": pen.color().alpha(),
                                "rgba": color_rgba(pen.color()),
                                "width_scene": pen.widthF(),
                                "qt_pen_is_cosmetic": pen.isCosmetic(),
                                "pen_style": pen.style().value,
                                "pen_brush_style": pen.brush().style().value,
                                "brush_style": item.brush().style().value,
                                "effective_opacity": item.effectiveOpacity(),
                                "scene_transform": [
                                    transform.m11(),
                                    transform.m12(),
                                    transform.m13(),
                                    transform.m21(),
                                    transform.m22(),
                                    transform.m23(),
                                    transform.m31(),
                                    transform.m32(),
                                    transform.m33(),
                                ],
                            }
                        )
        paths.sort(key=lambda path: json.dumps(path, sort_keys=True))
        faces.sort(key=lambda face: json.dumps(face, sort_keys=True))
        return {"paths": paths, "faces": faces, "rectangles": rectangles}

    def pre_export_evidence(name, device, baseline_closes):
        required = {
            "distance": 1,
            "theoretical-exact": 1,
            "area-and-theoretical-exact": 2,
            "area-relocated-and-theoretical-exact": 2,
        }.get(name, 0)
        readiness_path = output / ("face-readiness-" + device + "-" + name + ".json")
        assert not readiness_path.exists(), "Preserve face readiness diagnostics"
        readiness_states = []

        def observe_face_readiness(state):
            if not readiness_states or state != readiness_states[-1]:
                if len(readiness_states) == 20:
                    readiness_states[-1] = state
                else:
                    readiness_states.append(state)
                readiness_path.write_text(json.dumps(readiness_states, indent=2) + "\n")
                print("FACE_READINESS_STATE", device, name, state)
                log.flush()

        scene, readiness = wait_for_box_face(
            scene_record,
            view.requestPaint,
            QtCore.QThreadPool.globalInstance().activeThreadCount,
            settle,
            observe_face_readiness,
            time.monotonic,
        )
        palette = text_palette_record()
        expectation = null_origin_frame_expectation(scene, palette, required)
        assert digest(macro_path) == macro_source["sha256"], "Macro source changed before export"
        evidence = {
            "phase": "before-stock-command",
            "macro_source": macro_source,
            "device": device,
            "scenario": name,
            "pdf_version": preferences["Mod"].GetInt("PDFVersion", 0),
            "text_palette": palette,
            "scene": scene,
            "face_readiness": readiness,
            "null_origin_frame_expectation": expectation,
            "baseline_invalid_closes": baseline_closes + expectation["baseline_invalid_closes"],
        }
        assert required == 0 or evidence["pdf_version"] == 0, evidence
        path = output / ("pre-export-" + device + "-" + name + ".json")
        assert not path.exists(), "Preserve prospective input evidence"
        path.write_text(json.dumps(evidence, indent=2) + "\n")
        print("PRE_EXPORT_EVIDENCE", device, name, evidence)
        log.flush()
        return evidence

    def post_export_scene(evidence):
        scene = scene_record()
        assert ready_box_face(scene), scene
        assert scene["faces"] == evidence["scene"]["faces"], (evidence, scene["faces"])
        palette = text_palette_record()
        assert palette == evidence["text_palette"], (evidence, palette)
        expectation = null_origin_frame_expectation(
            scene,
            palette,
            evidence["null_origin_frame_expectation"]["required_count"],
        )
        assert expectation == evidence["null_origin_frame_expectation"], (evidence, expectation)
        return scene

    def export_printer(name, baseline_closes):
        pdf = output / ("qprinter-" + name + ".pdf")
        assert not pdf.exists()
        before = preferences["View"].GetBool("ScreenMode", True)
        dialogs = []
        printer_settings = []
        native_ui_settings = []
        callback_errors = []
        panel_states = []
        observed_states = set()
        panel_window = []
        diagnostic_file = output / ("qprinter-" + name + "-diagnostics.json")
        version = preferences["Mod"].GetInt("PDFVersion", 0)
        pdf_version = {
            0: QtGui.QPagedPaintDevice.PdfVersion_1_4,
            1: QtGui.QPagedPaintDevice.PdfVersion_A1b,
        }[version]
        timer = QtCore.QTimer()
        timer.setInterval(100)

        def record_print_state(stage, state=None):
            value = {
                "stage": stage,
                "visible_qt_dialogs": [
                    widget.metaObject().className()
                    for widget in QtWidgets.QApplication.instance().topLevelWidgets()
                    if isinstance(widget, QtPrintSupport.QPrintDialog) and widget.isVisible()
                ],
            }
            if sys.platform == "darwin":
                value["cocoa"] = state if state is not None else cocoa_print_panel_state()
            elif sys.platform == "win32":
                value["windows"] = state if state is not None else windows_print_panel_state()
            key = json.dumps(value, sort_keys=True)
            if key not in observed_states:
                observed_states.add(key)
                if len(panel_states) == 20:
                    panel_states[-1] = value
                else:
                    panel_states.append(value)
                print("PRINT_DIALOG_STATE", name, value)
                log.flush()
                diagnostic_file.write_text(json.dumps(panel_states, indent=2) + "\n")

        def fatal_print_failure(reason):
            try:
                print("PRINT_FATAL", name, reason)
                record_print_state("fatal: " + reason)
            except Exception:
                try:
                    traceback.print_exc()
                except Exception:
                    pass  # A failed log must still terminate this disposable process.
            finally:
                try:
                    log.flush()
                finally:
                    os._exit(1)

        def configure_printer(dialog):
            printer = dialog.printer()
            printer.setOutputFormat(QtPrintSupport.QPrinter.PdfFormat)
            printer.setOutputFileName(str(pdf))
            printer.setResolution(1200)
            printer.setPdfVersion(pdf_version)
            printer.setFullPage(True)
            printer.setColorMode(QtPrintSupport.QPrinter.Color)
            assert printer.outputFormat() == QtPrintSupport.QPrinter.PdfFormat
            assert Path(printer.outputFileName()).resolve() == pdf.resolve()
            assert printer.resolution() == 1200 and printer.pdfVersion() == pdf_version
            assert printer.fullPage()
            printer_settings.append(
                {
                    "format": printer.outputFormat().value,
                    "file": printer.outputFileName(),
                    "resolution": printer.resolution(),
                    "pdf_version": printer.pdfVersion().value,
                    "full_page": printer.fullPage(),
                }
            )

        def accept_print_dialog():
            visible_dialogs = [
                widget
                for widget in QtWidgets.QApplication.instance().topLevelWidgets()
                if isinstance(widget, QtPrintSupport.QPrintDialog) and widget.isVisible()
            ]
            if sys.platform == "win32":
                state = windows_print_panel_state()
                record_print_state("poll", state)
                assert len(visible_dialogs) <= 1, "Expected one visible stock Print dialog"
                if not visible_dialogs or not ready_windows_print_panel(state):
                    return
                panel_window.append(windows_print_panel_candidates(state)[0])
                assert len(panel_window) == 1, "Expected one owned Windows Print panel"
                record_print_state("owned Print panel active", state)
            for widget in visible_dialogs:
                if sys.platform == "darwin":
                    state = cocoa_print_panel_state()
                    record_print_state("poll", state)
                    assert len(visible_dialogs) == 1, "Expected one visible stock Print dialog"
                    # Qt makes the wrapper visible, then processes events before
                    # AppKit enters runModal. Keep polling through that interval.
                    if not ready_cocoa_print_panel(state):
                        return
                    panel_window.append(state["window"])
                    assert len(panel_window) == 1, "Expected one owned Cocoa Print panel"
                    record_print_state("owned Print panel active", state)
                dialogs.append(widget.metaObject().className())
                post_export_scene(evidence)

                # The native dialog can map destination settings before emitting
                # accepted; keep this actual printer configured for PDF afterward.
                def accepted():
                    try:
                        configure_printer(widget)
                        record_print_state("accepted printer configured")
                    except Exception:
                        # Do not continue stock printing with a failed PDF setup.
                        traceback.print_exc()
                        fatal_print_failure("accepted PDF printer configuration failed")

                widget.accepted.connect(accepted)
                try:
                    if sys.platform == "win32":
                        # Qt caches the native engine through PrintDlgEx's
                        # readback. Replace it only in accepted(), after that
                        # readback and before stock PagePrinter receives it.
                        assert (
                            widget.printer().outputFormat() == QtPrintSupport.QPrinter.NativeFormat
                        )
                        native_ui_settings.append({"format": widget.printer().outputFormat().value})
                    else:
                        configure_printer(widget)
                    record_print_state("initial printer configured")
                    timer.stop()
                    if sys.platform == "darwin":
                        record_print_state("Cocoa completion requested")
                        accept_cocoa_print_panel(1, panel_window[0])
                    elif sys.platform == "win32":
                        native_ui_settings[-1].update(accept_windows_print_panel(panel_window[0]))
                    else:
                        widget.accept()
                except Exception:
                    callback_errors.append(traceback.format_exc())
                    traceback.print_exc()
                    timer.stop()
                    if sys.platform == "win32":
                        fatal_print_failure("native Windows printer callback failed")
                    elif sys.platform == "darwin":
                        try:
                            record_print_state("cancel after callback failure")
                            accept_cocoa_print_panel(0, panel_window[0])
                        except Exception:
                            traceback.print_exc()
                            fatal_print_failure("owned Cocoa Print panel cancellation failed")
                    else:
                        widget.reject()
                return

        def observe_print_dialog():
            try:
                accept_print_dialog()
            except Exception:
                callback_errors.append(traceback.format_exc())
                traceback.print_exc()
                timer.stop()
                if sys.platform in ("darwin", "win32"):
                    fatal_print_failure("native Print dialog observation failed")
                for widget in QtWidgets.QApplication.instance().topLevelWidgets():
                    if isinstance(widget, QtPrintSupport.QPrintDialog) and widget.isVisible():
                        widget.reject()

        timer.timeout.connect(observe_print_dialog)
        watchdog = QtCore.QTimer()
        watchdog.setSingleShot(True)

        def reject_print_timeout():
            timer.stop()
            if sys.platform in ("darwin", "win32"):
                # The disposable process must not leave a native modal panel open.
                fatal_print_failure("native Print panel watchdog timed out")
            for widget in QtWidgets.QApplication.instance().topLevelWidgets():
                if isinstance(widget, QtPrintSupport.QPrintDialog) and widget.isVisible():
                    widget.reject()

        watchdog.timeout.connect(reject_print_timeout)
        preferences["View"].SetBool("ScreenMode", False)
        try:
            evidence = pre_export_evidence(name, "qprinter", baseline_closes)
            timer.start()
            watchdog.start(20000)
            Gui.runCommand("Std_Print")
            record_print_state("stock print command returned")
        finally:
            timer.stop()
            watchdog.stop()
            preferences["View"].SetBool("ScreenMode", before)
        assert dialogs == ["QPrintDialog"], dialogs
        assert not callback_errors, callback_errors
        assert pdf.exists() and pdf.stat().st_size > 1000
        assert printer_settings and printer_settings[-1]["format"] == 1
        return pdf, {
            "stock_dialog": dialogs,
            "printer_settings": printer_settings,
            "native_ui_settings": native_ui_settings,
            "pre_export_evidence": evidence,
            **post_export_scene(evidence),
            "panel_states": panel_states,
            "screen_mode_before_during_after": [before, False, before],
            "native_panel_acceptance": {
                "darwin": "NSApplication.stopModalWithCode",
                "win32": "EnumThreadWindows/owned Print BM_CLICK",
            }.get(sys.platform, "QPrintDialog.accept"),
        }

    def export(name, baseline_closes):
        pdf = output / (name + ".pdf")
        assert not pdf.exists()
        before = preferences["View"].GetBool("ScreenMode", True)
        pdf_version = preferences["Mod"].GetInt("PDFVersion", 0)
        assert before, "Exercise the command's temporary physical print mode"
        dialogs = []
        selected_files = []
        staged = []
        owned_dialog = []
        dialog_states = []
        callback_errors = []
        timer = QtCore.QTimer()
        timer.setInterval(100)

        def record_pdf_dialog(widget, stage):
            editor = widget.findChild(QtWidgets.QLineEdit, "fileNameEdit")
            state = {
                "stage": stage,
                "class": widget.metaObject().className(),
                "directory": widget.directory().absolutePath(),
                "selected_files": widget.selectedFiles(),
                "filename_text": editor.text() if editor is not None else None,
                "filename_has_focus": editor.hasFocus() if editor is not None else None,
            }
            dialog_states.append(state)
            print("PDF_DIALOG_STATE", name, state)

        def accept_pdf_dialog():
            for widget in QtWidgets.QApplication.instance().topLevelWidgets():
                if (
                    isinstance(widget, QtWidgets.QFileDialog)
                    and widget.isVisible()
                    and widget.metaObject().className() == "Gui::FileDialog"
                ):
                    try:
                        if not staged:
                            owned_dialog.append(widget)
                            widget.setDirectory(str(output))
                            staged.append("directory")
                            record_pdf_dialog(widget, "directory")
                            return
                        assert widget is owned_dialog[0], "Stock PDF dialog changed"
                        if staged == ["directory"]:
                            # Qt selectFile leaves a focused filename edit untouched.
                            # Clear only this dialog's focus before selecting the name,
                            # on a separate turn from the directory model update.
                            focused = QtWidgets.QApplication.focusWidget()
                            if focused is not None and widget.isAncestorOf(focused):
                                focused.clearFocus()
                            widget.selectFile(pdf.name)
                            staged.append("filename")
                            record_pdf_dialog(widget, "filename")
                            return
                        selected = widget.selectedFiles()
                        record_pdf_dialog(widget, "accept")
                        assert len(selected) == 1 and Path(selected[0]).resolve() == pdf.resolve()
                        post_export_scene(evidence)
                        selected_files.append(selected)
                        dialogs.append(widget.metaObject().className())
                        timer.stop()
                        watchdog.stop()
                        widget.accept()
                    except Exception:
                        callback_errors.append(traceback.format_exc())
                        traceback.print_exc()
                        timer.stop()
                        watchdog.stop()
                        widget.reject()
                    return

        timer.timeout.connect(accept_pdf_dialog)
        watchdog = QtCore.QTimer()
        watchdog.setSingleShot(True)

        def reject_timeout():
            timer.stop()
            callback_errors.append("Timed out while staging the stock PDF dialog")
            if owned_dialog:
                record_pdf_dialog(owned_dialog[0], "timeout")
                owned_dialog[0].reject()
            else:
                print(callback_errors[-1])
                log.flush()
                os._exit(1)

        watchdog.timeout.connect(reject_timeout)
        evidence = pre_export_evidence(name, "qpdfwriter", baseline_closes)
        timer.start()
        watchdog.start(20000)
        Gui.runCommand("TechDraw_ExportPagePDF")
        timer.stop()
        watchdog.stop()
        assert not callback_errors, callback_errors
        assert dialogs == ["Gui::FileDialog"], dialogs
        if not pdf.exists():
            print("ACTIVE_VIEW", Gui.activeDocument().activeView())
            for widget in Gui.getMainWindow().findChildren(QtWidgets.QTextEdit):
                if widget.toPlainText():
                    print(
                        "REPORT_WIDGET",
                        widget.metaObject().className(),
                        widget.toPlainText(),
                    )
        assert pdf.exists() and pdf.stat().st_size > 1000
        assert preferences["View"].GetBool("ScreenMode", True) == before
        cases.append(
            {
                "name": "qpdfwriter:" + name,
                "device": "qpdfwriter",
                "scenario": name,
                "pdf": pdf.name,
                "expect_ink": True,
                "expected_color": "",
                "baseline_invalid_closes": evidence["baseline_invalid_closes"],
                "pdf_version": pdf_version,
            }
        )
        records.append(
            {
                "name": name,
                "device": "qpdfwriter",
                "stock_dialog": dialogs,
                "selected_files": selected_files,
                "file_dialog_states": dialog_states,
                "screen_mode_before_after": [before, before],
                "pre_export_evidence": evidence,
                **post_export_scene(evidence),
            }
        )
        print("EXPORTED", "qpdfwriter", name, evidence["baseline_invalid_closes"])
        printer_pdf, printer_record = export_printer(name, baseline_closes)
        cases.append(
            {
                "name": "qprinter:" + name,
                "device": "qprinter",
                "scenario": name,
                "pdf": printer_pdf.name,
                "expect_ink": True,
                "expected_color": "",
                "baseline_invalid_closes": printer_record["pre_export_evidence"][
                    "baseline_invalid_closes"
                ],
                "pdf_version": pdf_version,
            }
        )
        records.append({"name": name, "device": "qprinter", **printer_record})
        print(
            "EXPORTED",
            "qprinter",
            name,
            printer_record["pre_export_evidence"]["baseline_invalid_closes"],
        )

    def set_gui_style(line_number):
        Gui.Selection.clearSelection()
        Gui.Selection.addSelection(document.Name, view.Name, selection_name)
        Gui.runCommand("TechDraw_DecorateLine")
        settle()
        task = Gui.Control.activeTaskDialog()
        assert task is not None
        styles = [
            widget.findChild(QtWidgets.QComboBox, "cb_Style") for widget in task.getDialogContent()
        ]
        styles = [style for style in styles if style is not None]
        assert len(styles) == 1 and styles[0].count() == 17
        styles[0].setCurrentIndex(line_number - 1)
        task.accept()
        settle()
        assert not Gui.Control.activeDialog()
        view.touch()
        document.recompute()
        settle()

    export("box-only", 0)
    tag = view.makeCosmeticLine(
        App.Vector(20, 20, 0), App.Vector(20.01, 20, 0), 1, 0.2, (0.0, 0.0, 0.0, 0.5)
    )
    edge = view.getCosmeticEdge(tag)
    view.touch()
    document.recompute()
    settle()
    selection_name = None
    for index in range(100):
        candidate = "Edge" + str(index)
        try:
            if view.getCosmeticEdgeBySelection(candidate).Tag == tag:
                selection_name = candidate
                break
        except ValueError:
            pass
    assert selection_name is not None
    set_gui_style(10)  # Shipped ASME Viewing-plane line.
    export("short-gap", 1)
    document.saveAs(str(output / "short-gap.FCStd"))
    edge.Format = {
        "style": edge.Format["style"],
        "weight": 0.2,
        "color": (0.0, 0.0, 0.0, 1.0),
        "visible": True,
    }
    view.touch()
    document.recompute()
    settle()
    export("short-gap-opaque", 0)
    edge.Format = {
        "style": edge.Format["style"],
        "weight": 0.2,
        "color": (0.0, 0.0, 0.0, 0.5),
        "visible": True,
    }
    set_gui_style(1)
    export("short-solid", 0)
    set_gui_style(10)
    edge.End = edge.Start + App.Vector(10, 0, 0)
    view.touch()
    document.recompute()
    settle()
    export("long-dashed", 0)
    edge.End = edge.Start + App.Vector(0.25, 0, 0)
    edge.Format = {
        "style": edge.Format["style"],
        "weight": 0.0,
        "color": (0.0, 0.0, 0.0, 0.5),
        "visible": True,
    }
    view.touch()
    document.recompute()
    settle()
    export("zero-width-translucent", 0)
    edge.End = edge.Start + App.Vector(10, 0, 0)
    edge.Format = {**edge.Format, "color": (0.0, 0.0, 0.0, 1.0)}
    view.touch()
    document.recompute()
    settle()
    export("zero-width-opaque", 0)
    edge.Format = {**edge.Format, "color": (0.0, 0.0, 0.0, 0.5)}
    preferences["Mod"].SetInt("PDFVersion", 1)
    view.touch()
    document.recompute()
    settle()
    export("zero-width-archival", 0)
    preferences["Mod"].SetInt("PDFVersion", 0)
    edge.Format = {**edge.Format, "visible": False}
    view.touch()
    document.recompute()
    preferences["Colors"].SetUnsigned("NormalColor", 0x000000D8)
    distance = document.addObject("TechDraw::DrawViewDimension", "Distance")
    distance.Type = "Distance"
    distance.References2D = [(view, "Edge1")]
    distance.X = 0
    distance.Y = -15
    page.addView(distance)
    document.recompute()
    settle(500)
    assert "Up-to-date" in distance.State
    export("distance", 0)
    distance.TheoreticalExact = True
    document.recompute()
    settle()
    export("theoretical-exact", 0)
    area = document.addObject("TechDraw::DrawViewDimension", "Area")
    area.Type = "Area"
    area.References2D = [(view, "Face0")]
    area.X = 25
    area.Y = 15
    page.addView(area)
    document.recompute()
    settle(500)
    assert "Up-to-date" in area.State and abs(area.getRawValue() - 100) < 1e-9
    export("area-and-theoretical-exact", 0)
    area.UseAreaLeaderPoint = True
    area.AreaLeaderPoint = App.Vector(2, 3, 0)
    document.recompute()
    settle()
    assert abs(area.getRawValue() - 100) < 1e-9
    export("area-relocated-and-theoretical-exact", 0)
    document.saveAs(str(output / "dimension-controls.FCStd"))
    records.append({"area_value_mm2": area.getRawValue()})

    images = loaded_images()
    libraries = []
    plugins = []
    for image in images:
        path = Path(image)
        if "Qt6" in path.name and path.is_file():
            libraries.append(
                {
                    "loaded_path": image,
                    "real_path": str(path.resolve()),
                    "sha256": digest(path),
                }
            )
        elif path.is_file() and path.suffix.lower() in (".so", ".dll", ".dylib"):
            if QtCore.QPluginLoader(str(path)).metaData():
                plugins.append(
                    {
                        "loaded_path": image,
                        "real_path": str(path.resolve()),
                        "sha256": digest(path),
                    }
                )
    qt_gui = [
        entry
        for entry in libraries
        if Path(entry["real_path"]).name.lower().startswith(("libqt6gui.", "qt6gui."))
    ]
    assert len(qt_gui) == 1 and Path(qt_gui[0]["real_path"]).is_relative_to(qt_lib), qt_gui
    loaded_module = [
        path for path in images if Path(path).name.casefold() == module_path.name.casefold()
    ]
    assert len(loaded_module) == 1 and Path(loaded_module[0]).resolve() == module_path
    manifest = {
        "schema_version": 2,
        "qt_version": QtCore.qVersion(),
        "raster_dpi": 150,
        "cases": cases,
    }
    native_runtime_images = []
    if sys.platform == "win32":
        for name in images:
            path = Path(name)
            stem = path.name.casefold()
            if stem in (
                "freecad.exe",
                "freecadapp.dll",
                "freecadbase.dll",
                "freecadgui.dll",
                "techdrawgui.pyd",
            ) or (stem.startswith(("python3", "pyside6", "shiboken6")) and stem.endswith(".dll")):
                native_runtime_images.append(
                    {"real_path": str(path.resolve()), "sha256": digest(path)}
                )
    provenance = {
        "schema_version": 1,
        "freecad_version": App.Version(),
        "qt_version": QtCore.qVersion(),
        "expected_qt_version": expected_qt_version,
        "macro_source": macro_source,
        "native_runtime_images": native_runtime_images,
        "qt_libraries": libraries,
        "qt_plugins": plugins,
        "qpa_platform": QtGui.QGuiApplication.platformName(),
        "expected_plugin_dir": str(plugin_root),
        "expected_qt_prefix": str(qt_prefix),
        "expected_qt_lib": str(qt_lib),
        "module": str(module_path),
        "module_sha256": digest(module_path),
        "bypass_provenance": bypass,
        "records": records,
    }
    (output / "manifest.json").write_text(json.dumps(manifest, indent=2) + "\n")
    (output / "native-provenance.json").write_text(json.dumps(provenance, indent=2) + "\n")
    print("DONE", App.Version(), QtCore.qVersion(), qt_gui)
    exit_code = 0
except Exception:
    traceback.print_exc()
finally:
    for (group, kind, key, default, value), old in zip(settings, previous):
        getattr(preferences[group], "Set" + kind)(key, old)
    log.flush()
    os._exit(exit_code)
